module o-ran-e-node-b {
    yang-version 1.1;
    namespace "urn:o:ran:e:node:b";
    prefix enb;

    organization
      "O-RAN Alliance - WG6: Cloudification and orchestration";
    contact
      "WG Web: <https://www.o-ran.org>
       WG List:  <mailto:contact@o-ran.org>";
    description
      "This module contains a collection of YANG definitions for managing radio 
       access network (RAN) devices.";

    revision 2019-01-19 {
        description
          "Formal updates including renaming the module.";
        reference
          "O-RAN TR ???: A YANG Data Model for Radio Access Networks.
           ONF TR 512: Common Information Model (CoreModel).
           BBF TR-196 2.0.3 full";
    }
    revision 2018-11-27 {
        description
          "Updated and to be used only for ONAP PCI Optimization PoC 2018-09-20
           Incorporated container for fap-service and added pnf-name leaf node
           For respective nodes, changed min-elements from 1 to 0 make them 
           optional";
        reference
          "ONF TR ???: A YANG Data Model for Radio Access Networks.
           BBF TR-196 2.0.3 full";
    }
    revision 2018-04-08 {
        description
          "Initial version, used only for ONAP PoC 2018-06-25";
        reference
          "ONF TR ???: A YANG Data Model for Radio Access Networks.
           BBF TR-196 2.0.3 full";
    }

    grouping configuration-phy-cell-id-request {
        leaf fap-service-number-of-entries {
            type uint64;
            description
              "none";
        }
        list fap-service {
            key "alias";
            leaf alias {
                type string {
                    length "1..64";
                }
                description
                  "none";
            }
            leaf cid {
                type string {
                    length "0..52";
                }
                description
                  "none";
            }
            leaf phy-cell-id-in-use {
                type uint64;
                default "0";
                description
                  "none";
            }
            leaf pnf-name {
                type string {
                    length "0..256";
                }
                description
                  "PNF name ";
            }
            description
              "none";
        }
        description
          "none";
    }

    grouping configuration-phy-cell-id-response {
        leaf response-code {
            type string;
            description
              "none";
        }
        leaf response-message {
            type string;
            description
              "none";
        }
        description
          "none";
    }

    container radio-access {
        leaf fap-service-number-of-entries {
            type uint64;
            description
              "{{numentries}}";
            reference
              "BBF TR-196 2.0.3 full - FAPServiceNumberOfEntries";
        }
        list fap-service {
            key "alias";
            uses fap-service-g;
            container x-0005b9-lte {
                uses x-0005b9-lte-g;
                description
                  "none";
            }
            container cell-config {
                uses cell-config-g;
                description
                  "Container for object class FAPService.{i}.CellConfig.";
                container lte {
                    uses lte-g;
                    description
                      "Container for object class 
                       FAPService.{i}.CellConfig.LTE.";
                    container lte-ran {
                        uses lte-ran-g;
                        description
                          "Container for object class 
                           FAPService.{i}.CellConfig.LTE.RAN.";
                        container lte-ran-common {
                            uses lte-ran-common-g;
                            description
                              "Container for object class 
                               FAPService.{i}.CellConfig.LTE.RAN.Common.";
                        }
                        container lte-ran-rf {
                            uses lte-ran-rf-g;
                            description
                              "Container for object class 
                               FAPService.{i}.CellConfig.LTE.RAN.RF.";
                        }
                        container lte-ran-neighbor-list-in-use {
                            uses lte-ran-neighbor-list-in-use-g;
                            description
                              "Container for object class 
                               FAPService.{i}.CellConfig.LTE.RAN
                               .NeighborListInUse.";
                            list lte-ran-neighbor-list-in-use-lte-cell {
                                key "plmnid cid";
                                uses lte-ran-neighbor-list-in-use-lte-cell-g;
                                description
                                  "List of object class 
                                  FAPService.{i}.CellConfig.LTE.RAN
                                  .NeighborListInUse.LTECell.{i}.";
                            }
                        }
                    }
                }
            }
            description
              "List of object class FAPService.{i}.";
        }
        description
          "none";
    }

    grouping fap-service-g {
        description
          "The Femto Access Point (FAP) Service Object.";
        leaf alias {
            type string {
                length "1..64";
            }
            description
              "{{datatype|expand}}";
            reference
              "BBF TR-196 2.0.3 full - FAPService.{i}.Alias";
        }
        reference
          "BBF TR-196 2.0.3 full - FAPService.{i}.";
    }

    grouping x-0005b9-lte-g {
        leaf phy-cell-id-in-use {
            type uint64;
            default "0";
            description
              "none";
        }
        leaf pnf-name {
            type string {
                length "0..256";
            }
            description
              "PNF name ";
        }
        description
          "none";
    }

    grouping cell-config-g {
        description
          "This object contains parameters relating to configuring the FAP.";
        reference
          "BBF TR-196 2.0.3 full - FAPService.{i}.CellConfig.";
    }

    grouping lte-g {
        description
          "This object contains parameters relating to configuring the 
           LTE FAP.";
        leaf tunnel-number-of-entries {
            type uint64;
            description
              "{{numentries}}";
            reference
              "BBF TR-196 2.0.3 full - 
               FAPService.{i}.CellConfig.LTE.TunnelNumberOfEntries";
        }
        reference
          "BBF TR-196 2.0.3 full - FAPService.{i}.CellConfig.LTE.";
    }

    grouping lte-ran-g {
        description
          "This object contains parameters relating to the LTE RAN level 
          configuration.";
        reference
          "BBF TR-196 2.0.3 full - FAPService.{i}.CellConfig.LTE.RAN.";
    }

    grouping lte-ran-common-g {
        description
          "This object contains parameters relating to the common configuration 
           in LTE RAN.";
        leaf cell-identity {
            type string {
                length "0..52";
            }
            config false;
            description
              "Cell Identity as specified in 
               {{bibref|3GPP-TS.36.331|Section 6.3.4}}.";
            reference
              "BBF TR-196 2.0.3 full - 
               FAPService.{i}.CellConfig.LTE.RAN.Common.CellIdentity";
        }
        reference
          "BBF TR-196 2.0.3 full - FAPService.{i}.CellConfig.LTE.RAN.Common.";
    }

    grouping lte-ran-rf-g {
        description
          "This object contains parameters relating to the RF, see 
           {{bibref|3GPP-TS.32.592|Section 6.1.7.1}}.";
        leaf-list phy-cell-id {
            type string;
            config false;
            // min-elements 0;
            max-elements 512;
            description
              "{{list}} Each item is a physical cell ID with a numeric range 
               between 0 and 503 inclusive. Represents the list of physical 
               cell identities LTE FAP to choose from. In case there is more 
               than one item in the list, the first item contains the most 
               preferred value. As specified in 
               {{bibref|3GPP-TS.36.211|Section 6.11}}. The multiplicity of the 
               {{param}} values can also be expressed by defining a range using 
               \"..\" (two periods) between two values. In this case, the 
               combination of two values defines the lower-bound and 
               upper-bound of the range inclusive. If this notation is used, 
               then the list contains at least 2 items: \"<preferred-value>,
               <lower-bound>..<upper-bound>\". If LTE FAP supports 
               self-configuration capability for {{param}} and more than one 
               item is configured, then LTE FAP is expected to select one from 
               the list and overwrite this parameter containing only the one 
               selected. If LTE FAP does not support self-configuration 
               capability for {{param}} and more than one item is configured, 
               then accepts the first value and ignore the rest. If only one 
               item is configured regardless of the self-configuration 
               capability of , accepts the value as an explicit configuration 
               by the ACS.";
            reference
              "BBF TR-196 2.0.3 full - 
              FAPService.{i}.CellConfig.LTE.RAN.RF.PhyCellID";
        }
        reference
          "BBF TR-196 2.0.3 full - FAPService.{i}.CellConfig.LTE.RAN.RF.";
    }

    grouping lte-ran-phy-g {
        description
          "This object contains parameters relating to the physical layer level 
           configuration.";
        reference
          "BBF TR-196 2.0.3 full - FAPService.{i}.CellConfig.LTE.RAN.PHY.";
    }

    grouping lte-ran-neighbor-list-lte-cell-g {
        description
          "Table containing the E-UTRA (i.e. intra-RAT) cell list provided by 
           the ACS. The table contents MAY be added/deleted/modified during 
           operation, in which case these changes shall be reflected in the 
           broadcast information as soon as possible.";
        leaf enable {
            type boolean;
            config false;
            description
              "Enables or disables this entry.";
            reference
              "BBF TR-196 2.0.3 full - 
              FAPService.{i}.CellConfig.LTE.RAN.NeighborList
              .LTECell.{i}.Enable";
        }
        leaf alias {
            type string {
                length "1..64";
            }
            description
              "{{datatype|expand}}";
            reference
              "BBF TR-196 2.0.3 full - 
               FAPService.{i}.CellConfig.LTE.RAN.NeighborList
               .LTECell.{i}.Alias";
        }
        leaf must-include {
            type boolean;
            config false;
            description
              "Indicates whether this instance of the neighbor shall be 
               included or excluded in the FAP's NL configuration.";
            reference
              "BBF TR-196 2.0.3 full - FAPService.{i}.CellConfig.LTE.RAN.NeighborList.LTECell.{i}.MustInclude";
        }
        leaf plmnid {
            type string {
                length "0..6";
            }
            description
              "PLMN ID consists of Mobile Country Code (MCC) and Mobile Network 
               Code (MNC) {{bibref|3GPP-TS.23.003}}, {{bibref|3GPP-TS.24.008}}. 
               Mobile Country Code consists of three digits and uniquely 
               identifies the country of domicile of the subscriber. Mobile 
               Network Code consists of two or three digits and identifies the 
               Home PLMN within a country. For a 2-digit MNC the total string 
               length of {{param}} is 5.";
            reference
              "BBF TR-196 2.0.3 full - FAPService.{i}
              .CellConfig.LTE.RAN.NeighborList.LTECell.{i}.PLMNID";
        }
        leaf cid {
            type string {
                length "0..52";
            }
            description
              "Cell Identity. {{bibref|3GPP-TS.36.331|Section 6.3.4}}. 
               Combination of {{param|PLMNID}} and {{param}} constitutes the 
               Cell Global ID (CGI).";
            reference
              "BBF TR-196 2.0.3 full - FAPService.{i}
               .CellConfig.LTE.RAN.NeighborList.LTECell.{i}.CID";
        }
        leaf phy-cell-id {
            type uint64 {
                range "0..503";
            }
            config false;
            description
              "Physical cell ID, as specified in 
               {{bibref|3GPP-TS.36.211|Section 6.11}}.";
            reference
              "BBF TR-196 2.0.3 full - FAPService.{i}
               .CellConfig.LTE.RAN.NeighborList.LTECell.{i}.PhyCellID";
        }
        reference
          "BBF TR-196 2.0.3 full - FAPService.{i}
           .CellConfig.LTE.RAN.NeighborList.LTECell.{i}.";
    }

    grouping lte-ran-neighbor-list-in-use-g {
        description
          "This object contains parameters relating to the neighbor list used 
           by the FAP based on its self-configuration capability and 
           {{object|.CellConfig.LTE.RAN.NeighborList.}} configuration of adding 
           and excluding cells.";
        leaf max-lte-cell-entries {
            type uint64;
            description
              "The maximum number of entries in the 
               {{object|.CellConfig.LTE.RAN.NeighborListInUse.LTECell.{i}.}} 
               table.";
            reference
              "BBF TR-196 2.0.3 full - FAPService.{i}
              .CellConfig.LTE.RAN.NeighborListInUse.MaxLTECellEntries";
        }
        leaf lte-cell-number-of-entries {
            type uint64;
            description
              "{{numentries}}";
            reference
              "BBF TR-196 2.0.3 full - FAPService.{i}
              .CellConfig.LTE.RAN.NeighborListInUse.LTECellNumberOfEntries";
        }
        reference
          "BBF TR-196 2.0.3 full - FAPService.{i}
           .CellConfig.LTE.RAN.NeighborListInUse.";
    }

    grouping lte-ran-neighbor-list-in-use-lte-cell-g {
        description
          "Table containing the LTE EUTRA (i.e. intra-RAT) cell list.";
        leaf plmnid {
            type string {
                length "0..6";
            }
            description
              "PLMN ID consists of Mobile Country Code (MCC) and Mobile Network 
               Code (MNC) {{bibref|3GPP-TS.23.003}}, {{bibref|3GPP-TS.24.008}}. 
               Mobile Country Code consists of three digits and uniquely 
               identifies the country of domicile of the subscriber. Mobile 
               Network Code consists of two or three digits and identifies the 
               Home PLMN within a country. For a 2-digit MNC the total string 
               length of {{param}} is 5.";
            reference
              "BBF TR-196 2.0.3 full - FAPService.{i}
               .CellConfig.LTE.RAN.NeighborListInUse.LTECell.{i}.PLMNID";
        }
        leaf cid {
            type string {
                length "0..52";
            }
            description
              "Cell Identity. {{bibref|3GPP-TS.36.331|Section 6.3.4}}. 
               Combination of {{param|PLMNID}} and {{param}} constitutes the 
               Cell Global ID (CGI).";
            reference
              "BBF TR-196 2.0.3 full - FAPService.{i}
               .CellConfig.LTE.RAN.NeighborListInUse.LTECell.{i}.CID";
        }
        leaf phy-cell-id {
            type uint64 {
                range "0..503";
            }
            description
              "Physical cell ID, as specified in 
               {{bibref|3GPP-TS.36.211|Section 6.11}}.";
            reference
              "BBF TR-196 2.0.3 full - FAPService.{i}
               .CellConfig.LTE.RAN.NeighborListInUse.LTECell.{i}.PhyCellID";
        }
        leaf pnf-name {
            type string {
                length "0..256";
            }
            description
              "PNF name ";
        }
        reference
          "BBF TR-196 2.0.3 full - FAPService.{i}
           .CellConfig.LTE.RAN.NeighborListInUse.LTECell.{i}.";
    }

    notification nbrlist-change-notification {
        description
          "RAN Neighbor List change notification.";
        leaf fap-service-number-of-entries-changed {
            type uint64;
            description
              "Number of cells for which neighbor list has changed";
        }
        list fap-service {
            key "alias";
            leaf alias {
                type string {
                    length "1..64";
                }
                description
                  "none";
            }
            leaf cid {
                type string {
                    length "0..52";
                }
                description
                  "none";
            }
            leaf lte-cell-number-of-entries {
                type uint64;
                description
                  "Number of cells in a neighbor list that was changed";
            }
            list lte-ran-neighbor-list-in-use-lte-cell-changed {
                key "plmnid cid";
                uses lte-ran-neighbor-list-in-use-lte-cell-g;
                description
                  "Changed/Modified List of cells in a neighbor list for this 
                   fap service";
            }
            description
              "none";
        }
    }

    typedef edit-operation-type {
        type enumeration {
            enum merge {
                value 0;
                description
                  "The configuration data identified by the                    
                   element containing this attribute is merged
                   with the configuration at the corresponding
                   level in the configuration datastore identified
                   by the target parameter.";
            }
            enum replace {
                value 1;
                description
                  "The configuration data identified by the element
                   containing this attribute replaces any related
                   configuration in the configuration datastore
                   identified by the target parameter.  If no such
                   configuration data exists in the configuration
                   datastore, it is created.  Unlike a
                   <copy-config> operation, which replaces the
                   entire target configuration, only the configuration
                   actually present in the config parameter is affected.";
            }
            enum create {
                value 2;
                description
                  "The configuration data identified by the element
                   containing this attribute is added to the
                   configuration if and only if the configuration
                   data does not already exist in the configuration
                   datastore.  If the configuration data exists, an
                   <rpc-error> element is returned with an
                   <error-tag> value of 'data-exists'.";
            }
            enum delete {
                value 3;
                description
                  "The configuration data identified by the element
                   containing this attribute is deleted from the
                   configuration if and only if the configuration
                   data currently exists in the configuration
                   datastore.  If the configuration data does not
                   exist, an <rpc-error> element is returned with
                   an <error-tag> value of 'data-missing'.";
            }
            enum remove {
                value 4;
                description
                  "The configuration data identified by the element
                   containing this attribute is deleted from the
                   configuration if the configuration
                   data currently exists in the configuration
                   datastore.  If the configuration data does not
                   exist, the 'remove' operation is silently ignored
                   by the server.";
            }
        }
        default "merge";
        description
          "NETCONF 'operation' attribute values";
        reference
          "RFC 6241, Section 7.2";
    }

    notification netconf-config-change {
        description
          "Generated when the NETCONF server detects that the
           <running> or <startup> configuration datastore
           has been changed by a management session.
           The notification summarizes the edits that
           have been detected.
           
           The server MAY choose to also generate this
           notification while loading a datastore during the
           boot process for the device.";
        leaf datastore {
            type enumeration {
                enum running {
                    description
                      "The <running> datastore has changed.";
                }
                enum startup {
                    description
                      "The <startup> datastore has changed";
                }
            }
            default "running";
            description
              "Indicates which configuration datastore has changed.";
        }
        list edit {
            description
              "An edit record SHOULD be present for each distinct
               edit operation that the server has detected on
               the target datastore.  This list MAY be omitted
               if the detailed edit operations are not known.
               The server MAY report entries in this list for
               changes not made by a NETCONF session (e.g., CLI).";
            leaf target {
                type instance-identifier;
                description
                  "Topmost node associated with the configuration change.
                   A server SHOULD set this object to the node within
                   the datastore that is being altered.  A server MAY
                   set this object to one of the ancestors of the actual
                   node that was changed, or omit this object, if the
                   exact node is not known.";
            }
            leaf operation {
                type edit-operation-type;
                description
                  "Type of edit operation performed.
                   A server MUST set this object to the NETCONF edit
                   operation performed on the target datastore.";
            }
        }
    }
}
